; Plugin para altrar as cotas e as legendas de uma vez através do comando

(defun C:20 ()
    (command "-dimstyle" "restore" "COTAS_1-20")
    (command "_CMLEADERSTYLE" "1-20")
)
(defun C:25 ()
    (command "-dimstyle" "restore" "COTAS_1-25")
    (command "_CMLEADERSTYLE" "1-25")
)
(defun C:50 ()
    (command "-dimstyle" "restore" "COTAS_1-50")
    (command "_CMLEADERSTYLE" "1-50")
)
(defun C:75 ()
    (command "-dimstyle" "restore" "COTAS_1-75")
    (command "_CMLEADERSTYLE" "1-75")
)
(defun C:100 ()
    (command "-dimstyle" "restore" "COTAS_1-100")
    (command "_CMLEADERSTYLE" "1-100")
)
